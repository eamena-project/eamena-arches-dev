FME workspace qdgc_export_to_geopackage.fmw

Parameters:
- SourceDataset_POSTGIS = qdgc@postgis13@localhost   # Connection
- DestDataset_OGCGEOPACKAGE = $(FME_MF_DIR)output   # GeoPackage File

Readers:
- POSTGIS_1: POSTGIS from $(SourceDataset_POSTGIS)

Writers:
- OGCGEOPACKAGE_1: OGCGEOPACKAGE to $(DestDataset_OGCGEOPACKAGE)

tbl_qdgc (reader POSTGIS_1)
    attributes: qdgc varchar(20), area_reference varchar(50), level_qdgc int4, cellsize_degrees numeric(1000,500), lon_center numeric(1000,500), lat_center numeric(1000,500), area_km2 numeric(1000,500)
    -> Reprojector
Reprojector
    DEST = EPSG:4326
    INTERPOLATION_TYPE_NAME = Nearest Neighbor
    RASTER_CELL_SIZE = Preserve Cells
    RASTER_TOLERANCE = 0.0
    SOURCE = Read from feature
    REPROJECTED -> AttributeCreator
AttributeCreator
    ATTR_TABLE = SET_TO filename = tbl_qdgc_@LowerCase(@Value(area_reference))
    -> StringCaseChanger
StringCaseChanger
    ATTRCHOICE = Selected Attributes
    ATTRLIST = area_reference
    CHANGE_TYPE = lowercase
    -> AttributeCreator_2
AttributeCreator_2
    ATTR_TABLE = SET_TO tablename_export = @Value(level_qdgc)
    -> StringPadder
StringPadder
    BLANK_ATTRIBUTE = Yes
    PADCHAR = 0
    SIDE = Left
    SRC_ATTRS = tablename_export
    WIDTH = 2
    -> TestFilter
TestFilter
    DEFAULT_VALUE = <UNFILTERED>
    TEST_LIST = "BOOL_OP,OR,COMPOSITE_TEST,""""""1"""""",TEST_CLAUSE,TEST @Value(level_qdgc) = 1",@Value(cellsize_degrees) = 1,"BOOL_OP,OR,COMPOSITE_TEST,""""""1"""""",TEST_CLAUSE,TEST @Value(level_qdgc) = 2",@Value(cellsize_degrees) = 2,"BOOL_OP,OR,COMPOSITE_TEST,""""""1"""""",TEST_CLAUSE,TEST @Value(level_qdgc) = 3",@Value(cellsize_degrees) = 3,"BOOL_OP,OR,COMPOSITE_TEST,""""""1"""""",TEST_CLAUSE,TEST @Value(level_qdgc) = 4",@Value(cellsize_degrees) = 4,"BOOL_OP,OR,COMPOSITE_TEST,""""""1"""""",TEST_CLAUSE,TEST @Value(level_qdgc) = 5",@Value(cellsize_degrees) = 5,"BOOL_OP,OR,COMPOSITE_TEST,""""""1"""""",TEST_CLAUSE,TEST @Value(level_qdgc) = 6",@Value(cellsize_degrees) = 6,"BOOL_OP,OR,COMPOSITE_TEST,""""""1"""""",TEST_CLAUSE,TEST @Value(level_qdgc) = 7",@Value(cellsize_degrees) = 7,"BOOL_OP,OR,COMPOSITE_TEST,""""""1"""""",TEST_CLAUSE,TEST @Value(level_qdgc) = 8",@Value(cellsize_degrees) = 8,"BOOL_OP,OR,COMPOSITE_TEST,""""""1"""""",TEST_CLAUSE,TEST @Value(level_qdgc) = 9",@Value(cellsize_degrees) = 9,"BOOL_OP,OR,COMPOSITE_TEST,""""""1"""""",TEST_CLAUSE,TEST @Value(level_qdgc) = 10",@Value(cellsize_degrees) = 11,"BOOL_OP,OR,COMPOSITE_TEST,""""""1"""""",TEST_CLAUSE,TEST @Value(level_qdgc) = 11",@Value(cellsize_degrees) = 11,"BOOL_OP,OR,COMPOSITE_TEST,""""""1"""""",TEST_CLAUSE,TEST @Value(level_qdgc) = 12",@Value(cellsize_degrees) = 12
    @Value(cellsize_degrees) = 1 -> public_tbl_qdgc (writer OGCGEOPACKAGE_1)
    @Value(cellsize_degrees) = 2 -> public_tbl_qdgc (writer OGCGEOPACKAGE_1)
    @Value(cellsize_degrees) = 3 -> public_tbl_qdgc (writer OGCGEOPACKAGE_1)
    @Value(cellsize_degrees) = 4 -> public_tbl_qdgc (writer OGCGEOPACKAGE_1)
    @Value(cellsize_degrees) = 5 -> public_tbl_qdgc (writer OGCGEOPACKAGE_1)
    @Value(cellsize_degrees) = 6 -> public_tbl_qdgc (writer OGCGEOPACKAGE_1)
    @Value(cellsize_degrees) = 7 -> public_tbl_qdgc (writer OGCGEOPACKAGE_1)
    @Value(cellsize_degrees) = 8 -> public_tbl_qdgc (writer OGCGEOPACKAGE_1)
    @Value(cellsize_degrees) = 9 -> public_tbl_qdgc (writer OGCGEOPACKAGE_1)
    @Value(cellsize_degrees) = 11 -> public_tbl_qdgc (writer OGCGEOPACKAGE_1)
    @Value(cellsize_degrees) = 12 -> public_tbl_qdgc (writer OGCGEOPACKAGE_1)
public_tbl_qdgc (writer OGCGEOPACKAGE_1)
    attributes: qdgc text(20), level_qdgc mediumint, cellsize_degrees double, lon_center double, lat_center double, area_km2 double
